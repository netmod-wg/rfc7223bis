module example-ethernet {
  namespace "http://example.com/ethernet";
  prefix "eth";

  import ietf-interfaces {
    prefix if;
  }
  import iana-if-type {
    prefix ianaift;
  }

  // configuration and state parameters for Ethernet interfaces
  augment "/if:interfaces/if:interface" {
    when "if:type = 'ianaift:ethernetCsmacd'";

    container ethernet {
      container transmission {
        choice transmission-params {
          case auto {
            leaf auto-negotiate {
              type empty;
            }
          }
          case manual {
            container manual {
              leaf duplex {
                type enumeration {
                  enum "half";
                  enum "full";
                }
              }
              leaf speed {
                type enumeration {
                  enum "10Mb";
                  enum "100Mb";
                  enum "1Gb";
                  enum "10Gb";
                }
              }
            }
          }
        }
        leaf duplex {
          type enumeration {
            enum "half";
            enum "full";
          }
          config false;
        }
      }
      // other Ethernet-specific params...
    }
  }
}
